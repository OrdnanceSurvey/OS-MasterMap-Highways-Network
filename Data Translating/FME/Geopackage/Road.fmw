FME workspace Road.fmw

Parameters:
- SourceDataset_GML_3 = C:\Temp\Highways_Data\Highways_RoadsAndRAM_Road_001.gml.gz   # Source Geography Markup Language (GML) File(s)
- DestDataset_GEOPACKAGE =   # Destination GeoPackage File

Readers:
- GML_1: GML from $(SourceDataset_GML_3)

Writers:
- GEOPACKAGE_1: GEOPACKAGE to $(DestDataset_GEOPACKAGE)

Note: Change to local input
Road (reader GML_1)
    attributes: beginLifespanVersion xml_char(24), designatedName{}.DesignatedNameType.name xml_char(25), designatedName{}.DesignatedNameType.namingAuthority.ResponsibleAuthority.authorityName xml_char(16), designatedName{}.DesignatedNameType.namingAuthority.ResponsibleAuthority.identifier xml_decimal(5,0), inNetwork{}.owns xml_char(6), inNetwork{}.xlink_href xml_char(18), inspireId.Identifier.localId xml_decimal(17,0), inspireId.Identifier.namespace xml_char(19), link{}.owns xml_char(6), link{}.xlink_href xml_char(22), nationalRoadCode xml_char(6), reasonForChange xml_char(4), reasonForChange.codeSpace xml_char(47), roadClassification xml_char(9), roadClassification.codeSpace xml_char(59), validFrom xml_char(1), validFrom.nilReason xml_char(8), validFrom.xsi_nil xml_char(5)
    -> AttributeRenamer
Note: This is an example output, writer will need to be added for specific output
AttributeRenamer
    ATTR_LIST = inspireId.Identifier.localId,identifier,,inspireId.Identifier.versionId,versionId,,gml_id,TOID,
    -> ListExploder
    -> ListIndexer

Bookmark: Identifies the RoadLinks which are a part of the Road feature
ListExploder
    ATTR_ACCUM_MODE = Merge Incoming List
    ATTR_CONFLICT_RES = Use Original
    INDEX_ATTR = _element_index
    LIST_ATTR = link{}
    LIST_FOUND -> AttributeRenamer_8
AttributeRenamer_8
    ATTR_LIST = xlink_href,RoadLink_TOID,
    -> StringReplacer
Note: remove # from the / feature references
StringReplacer
    SRC_ATTRS = RoadLink_TOID
    FIND_TEXT = #
    REGEXP = no
    NO_MATCH = _FME_NO_OP_
    CASE = no
    -> Road_NetworkRef (writer GEOPACKAGE_1)
Road_NetworkRef (writer GEOPACKAGE_1)
    attributes: TOID text(20), RoadLink_TOID text(20)

Bookmark: designatedName
Note: Break designated name into a list. / Split into 2 attributes for final output
Note: designatedName1
ListIndexer
    PREFIX = designatedName1_
    INDEX = 0
    LIST_ATTR = designatedName{}
    -> AttributeRenamer_2
Note: designatedName1
AttributeRenamer_2
    ATTR_LIST = designatedName1_DesignatedNameType.name,designatedName1,,designatedName1_DesignatedNameType.name.xml_lang,designatedName1_Language,,designatedName1_DesignatedNameType.namingAuthority.ResponsibleAuthority.authorityName,designatedName1_Authority,,designatedName1_DesignatedNameType.namingAuthority.ResponsibleAuthority.identifier,designatedName1_AuthorityID,
    -> ListIndexer_2
Note: designatedName2
ListIndexer_2
    PREFIX = designatedName2_
    INDEX = 1
    LIST_ATTR = designatedName{}
    -> AttributeRenamer_3
Note: designatedName2
AttributeRenamer_3
    ATTR_LIST = designatedName2_DesignatedNameType.name,designatedName2,,designatedName2_DesignatedNameType.name.xml_lang,designatedName2_Language,,designatedName2_DesignatedNameType.namingAuthority.ResponsibleAuthority.authorityName,designatedName2_Authority,,designatedName2_DesignatedNameType.namingAuthority.ResponsibleAuthority.identifier,designatedName2_AuthorityID,
    -> DateFormatter

Bookmark: Create the Road feature
Note: Reformats date as DMY
DateFormatter
    INVALID_DATE_VALUE = FME_NULL_VALUE
    FMT = FME Date (%Y%m%d)
    DATE_ATTR = beginLifespanVersion,validFrom
    SRCFMT = Unknown - Automatic Detection
    -> Road (writer GEOPACKAGE_1)
Note: Red arrow indicates not all attributes currently populated in data
Road (writer GEOPACKAGE_1)
    attributes: TOID text(20), identifier text(37), versionId mediumint, beginLifespanVersion datetime, validFrom datetime, validTo datetime, localRoadCode text(10), nationalRoadCode text(10), designatedName1 text(120), designatedName1_Language text(3), designatedName1_Authority text(20), designatedName1_AuthorityID text(10), designatedName2 text(120), designatedName2_Language text(3), designatedName2_Authority text(20), designatedName2_AuthorityID text(10), localName text(120), descriptor text(120), reasonForChange text(32), roadClassification text(21)
