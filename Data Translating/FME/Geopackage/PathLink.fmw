FME workspace PathLink.fmw

Parameters:
- SourceDataset_GML = C:\Temp\Highways_Data\Paths\Bedford_PathLink.gml.gz   # Source Geography Markup Language (GML) File(s)
- DestDataset_GEOPACKAGE =   # Destination GeoPackage File

Readers:
- GML_1: GML from $(SourceDataset_GML)

Writers:
- GEOPACKAGE_1: GEOPACKAGE to $(DestDataset_GEOPACKAGE)

Note: Change input to local GML
PathLink (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xsi_nil xml_boolean, centrelineGeometry xml_geometry, fictitious xml_boolean, endNode.owns xml_boolean, endNode.nilReason xml_buffer, endNode.gml_remoteSchema xml_buffer, endNode.xlink_href xml_buffer, startNode.owns xml_boolean, startNode.nilReason xml_buffer, startNode.gml_remoteSchema xml_buffer, startNode.xlink_href xml_buffer, geographicalName.nilReason xml_buffer, geographicalName.xsi_nil xml_boolean, geographicalName.GeographicalName.language xml_buffer, geographicalName.GeographicalName.language.nilReason xml_buffer,
      geographicalName.GeographicalName.language.xsi_nil xml_boolean, geographicalName.GeographicalName.nativeness.owns xml_boolean, geographicalName.GeographicalName.nativeness.nilReason xml_buffer, geographicalName.GeographicalName.nativeness.gml_remoteSchema xml_buffer, geographicalName.GeographicalName.nativeness.xlink_href xml_buffer, geographicalName.GeographicalName.nativeness.xsi_nil xml_boolean, geographicalName.GeographicalName.nameStatus.owns xml_boolean, geographicalName.GeographicalName.nameStatus.nilReason xml_buffer, geographicalName.GeographicalName.nameStatus.gml_remoteSchema xml_buffer, geographicalName.GeographicalName.nameStatus.xlink_href xml_buffer, geographicalName.GeographicalName.nameStatus.xsi_nil xml_boolean, geographicalName.GeographicalName.sourceOfName xml_buffer, geographicalName.GeographicalName.sourceOfName.nilReason xml_buffer, geographicalName.GeographicalName.sourceOfName.xsi_nil xml_boolean, geographicalName.GeographicalName.pronunciation.nilReason xml_buffer, geographicalName.GeographicalName.pronunciation.xsi_nil xml_boolean, geographicalName.GeographicalName.pronunciation.PronunciationOfName.pronunciationSoundLink xml_buffer, geographicalName.GeographicalName.pronunciation.PronunciationOfName.pronunciationSoundLink.nilReason xml_buffer, geographicalName.GeographicalName.pronunciation.PronunciationOfName.pronunciationSoundLink.xsi_nil xml_boolean, geographicalName.GeographicalName.pronunciation.PronunciationOfName.pronunciationIPA xml_buffer, geographicalName.GeographicalName.pronunciation.PronunciationOfName.pronunciationIPA.nilReason xml_buffer, geographicalName.GeographicalName.pronunciation.PronunciationOfName.pronunciationIPA.xsi_nil xml_boolean, geographicalName.GeographicalName.spelling{}.SpellingOfName.text xml_buffer, geographicalName.GeographicalName.spelling{}.SpellingOfName.script xml_buffer, geographicalName.GeographicalName.spelling{}.SpellingOfName.script.nilReason xml_buffer, geographicalName.GeographicalName.spelling{}.SpellingOfName.script.xsi_nil xml_boolean, geographicalName.GeographicalName.spelling{}.SpellingOfName.transliterationScheme xml_buffer, geographicalName.GeographicalName.spelling{}.SpellingOfName.transliterationScheme.nilReason xml_buffer, geographicalName.GeographicalName.spelling{}.SpellingOfName.transliterationScheme.xsi_nil xml_boolean, geographicalName.GeographicalName.grammaticalGender.owns xml_boolean,
      geographicalName.GeographicalName.grammaticalGender.nilReason xml_buffer, geographicalName.GeographicalName.grammaticalGender.gml_remoteSchema xml_buffer, geographicalName.GeographicalName.grammaticalGender.xlink_href xml_buffer, geographicalName.GeographicalName.grammaticalGender.xsi_nil xml_boolean, geographicalName.GeographicalName.grammaticalNumber.owns xml_boolean, geographicalName.GeographicalName.grammaticalNumber.nilReason xml_buffer, geographicalName.GeographicalName.grammaticalNumber.gml_remoteSchema xml_buffer, geographicalName.GeographicalName.grammaticalNumber.xlink_href xml_buffer, geographicalName.GeographicalName.grammaticalNumber.xsi_nil xml_boolean, validFrom xml_datetime, validFrom.nilReason xml_buffer, validFrom.xsi_nil xml_boolean, validTo xml_datetime, validTo.nilReason xml_buffer, validTo.xsi_nil xml_boolean, reasonForChange xml_buffer, reasonForChange.codeSpace xml_buffer, formOfWay xml_buffer, formOfWay.codeSpace xml_buffer, pathName{} xml_buffer, pathName{}.xml_lang xml_buffer, alternateName{} xml_buffer, alternateName{}.xml_lang xml_buffer, provenance xml_buffer, provenance.codeSpace xml_buffer, surfaceType xml_buffer, surfaceType.codeSpace xml_buffer, cycleFacility.CycleFacilityType.cycleFacility xml_buffer, cycleFacility.CycleFacilityType.cycleFacility.codeSpace xml_buffer, cycleFacility.CycleFacilityType.wholeLink xml_boolean,
      cycleFacility.CycleFacilityType.wholeLink.nilReason xml_buffer, cycleFacility.CycleFacilityType.wholeLink.xsi_nil xml_boolean, matchStatus xml_buffer, matchStatus.codeSpace xml_buffer, length xml_real64, length.uom xml_buffer, alternateIdentifier{}.ThematicIdentifier.identifier xml_buffer, alternateIdentifier{}.ThematicIdentifier.identifierScheme xml_buffer, startGradeSeparation xml_int64, endGradeSeparation xml_int64, elevationGain.ElevationGainType.inDirection xml_real64, elevationGain.ElevationGainType.inDirection.uom xml_buffer, elevationGain.ElevationGainType.inOppositeDirection xml_real64, elevationGain.ElevationGainType.inOppositeDirection.uom xml_buffer, relatedArea{}.nilReason xml_buffer, relatedArea{}.gml_remoteSchema xml_buffer, relatedArea{}.xlink_href xml_buffer, relatedArea{}.owns xml_boolean, formsPartOf{}.nilReason xml_buffer, formsPartOf{}.gml_remoteSchema xml_buffer, formsPartOf{}.xlink_href xml_buffer, formsPartOf{}.owns xml_boolean
    -> AttributeRenamer
Note: Rename TOID
AttributeRenamer
    ATTR_LIST = gml_id,TOID,,inspireId.Identifier.localId,localId,,endNode.xlink_href,endNode,,startNode.xlink_href,startNode,
    -> DateFormatter
Note: Change output to prefered format
DateFormatter
    SRCFMT = Unknown - Automatic Detection
    INVALID_DATE_VALUE = FME_NULL_VALUE
    DATE_ATTR = beginLifespanVersion,validFrom
    FMT = FME Date (%Y%m%d)
    -> ListExploder
    -> ListExploder_2
    -> ListIndexer
    -> ListExploder_3

Bookmark: alternateIdentifier
ListExploder
    INDEX_ATTR = _element_index
    ATTR_CONFLICT_RES = Use Original
    ATTR_ACCUM_MODE = Merge Incoming List
    LIST_ATTR = alternateIdentifier{}
    LIST_FOUND -> AttributeRenamer_2
AttributeRenamer_2
    ATTR_LIST = ThematicIdentifier.identifier,alternateIdentifier,,ThematicIdentifier.identifierScheme,alternateIdentifierSchema,
    -> PathLnk_AlternateIdentifier (writer GEOPACKAGE_1)
PathLnk_AlternateIdentifier (writer GEOPACKAGE_1)
    attributes: TOID text(20), alternateIdentifier text(20), alternateIdentifierSchema text(50)

Bookmark: formsPartOf
ListExploder_2
    INDEX_ATTR = _element_index
    ATTR_CONFLICT_RES = Use Original
    ATTR_ACCUM_MODE = Merge Incoming List
    LIST_ATTR = formsPartOf{}
    LIST_FOUND -> TestFilter
TestFilter
    DEFAULT_VALUE = <UNFILTERED>
    TEST_LIST = BOOL_OP,OR,COMPOSITE_TEST,<Unused>,TEST_CLAUSE,"TEST @Value(xlink_href) CONTAINS #osgb",osgb,BOOL_OP,OR,COMPOSITE_TEST,<Unused>,TEST_CLAUSE,"TEST @Value(xlink_href) CONTAINS #usrn",usrn
    osgb -> AttributeCreator
    usrn -> AttributeCreator_2
    <UNFILTERED> -> AttributeCreator_3
AttributeCreator
    ATTR_LIST = refType,Road
    -> AttributeRenamer_9
AttributeCreator_2
    ATTR_LIST = refType,Street
    -> AttributeRenamer_9
AttributeCreator_3
    ATTR_LIST = refType,Other
    -> AttributeRenamer_9
AttributeRenamer_9
    ATTR_LIST = xlink_href,formsPartOf,
    -> StringReplacer_2
StringReplacer_2
    REGEXP = no
    NO_MATCH = _FME_NO_OP_
    SRC_ATTRS = formsPartOf
    FIND_TEXT = #
    CASE = no
    -> PathLink_FormsPartOf (writer GEOPACKAGE_1)
PathLink_FormsPartOf (writer GEOPACKAGE_1)
    attributes: TOID text(20), formsPartOf text(20), refType text(20)

Bookmark: PathLink
ListIndexer
    PREFIX = pathName1_
    LIST_ATTR = pathName{}
    INDEX = 0
    -> AttributeRenamer_3
AttributeRenamer_3
    ATTR_LIST = pathName1_pathName,pathName1_Text,,pathName1_xml_lang,pathName1_Language,
    -> ListIndexer_2
ListIndexer_2
    PREFIX = pathName2_
    LIST_ATTR = pathName{}
    INDEX = 1
    -> AttributeRenamer_4
AttributeRenamer_4
    ATTR_LIST = pathName2_pathName,pathName2_Text,,pathName2_xml_lang,pathName2_Language,
    -> ListIndexer_5
ListIndexer_5
    PREFIX = alternativeName1_
    LIST_ATTR = alternateName{}
    INDEX = 0
    -> AttributeRenamer_6
AttributeRenamer_6
    ATTR_LIST = alternativeName1_alternateName,alternativeName1_Text,,alternativeName1_xml_lang,alternativeName1_Language,
    -> ListIndexer_6
ListIndexer_6
    PREFIX = alternativeName2_
    LIST_ATTR = alternateName{}
    INDEX = 1
    -> AttributeRenamer_7
AttributeRenamer_7
    ATTR_LIST = alternativeName2_alternateName,alternativeName2_Text,,localName2_xml_lang,alternativeName2_Language,
    -> StringReplacer
Note: Remove #
StringReplacer
    REGEXP = no
    NO_MATCH = _FME_NO_OP_
    SRC_ATTRS = endNode,startNode
    FIND_TEXT = #
    CASE = no
    -> PathLink (writer GEOPACKAGE_1)
PathLink (writer GEOPACKAGE_1)
    attributes: TOID text(20), localId text(37), beginLifespanVersion datetime, validFrom datetime, fictitious text(5), startNode text(20), startGradeSeparation mediumint, endNode text(20), endGradeSeparation mediumint, reasonForChange text(32), formOfWay text(42), pathName1_Text text(255), pathName1_Language text(3), pathName2_Text text(255), pathName2_Language text(3), alternativeName1_Text text(255), alternativeName1_Language text(5), alternativeName2_Text text(255), alternativeName2_Language text(5), provenance text(23), surfaceType text(13), matchStatus text(39), length double

Bookmark: The OS MasterMap Topography Layer TOID reference that the RoadLink sits within
ListExploder_3
    INDEX_ATTR = _element_index
    ATTR_CONFLICT_RES = Use Original
    ATTR_ACCUM_MODE = Merge Incoming List
    LIST_ATTR = relatedArea{}
    LIST_FOUND -> AttributeRenamer_10
AttributeRenamer_10
    ATTR_LIST = xlink_href,RelatedRoadAreaTOID,
    -> StringReplacer_3
Note: remove # from the / feature references
StringReplacer_3
    REGEXP = no
    NO_MATCH = _FME_NO_OP_
    SRC_ATTRS = RelatedRoadAreaTOID
    FIND_TEXT = #
    CASE = no
    -> RoadLink_TopoTOIDRef (writer GEOPACKAGE_1)
RoadLink_TopoTOIDRef (writer GEOPACKAGE_1)
    attributes: TOID text(20), RelatedRoadAreaTOID text(39)
