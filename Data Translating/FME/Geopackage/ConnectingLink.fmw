FME workspace ConnectingLink.fmw

Parameters:
- SourceDataset_GML = C:\Temp\Highways_Data\Paths\Bedford_ConnectingLink.gml.gz   # Source Geography Markup Language (GML) File(s)
- DestDataset_GEOPACKAGE =   # Destination GeoPackage File

Readers:
- GML_1: GML from $(SourceDataset_GML)

Writers:
- GEOPACKAGE_1: GEOPACKAGE to $(DestDataset_GEOPACKAGE)

Note: Set input to local GML files
ConnectingLink (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xsi_nil xml_boolean, reasonForChange xml_buffer, reasonForChange.codeSpace xml_buffer, geometry xml_geometry, fictitious xml_boolean, pathNode.nilReason xml_buffer, pathNode.gml_remoteSchema xml_buffer, pathNode.xlink_href xml_buffer, pathNode.owns xml_boolean, connectingNode.nilReason xml_buffer, connectingNode.gml_remoteSchema xml_buffer, connectingNode.xlink_href xml_buffer, connectingNode.owns xml_boolean
    -> AttributeRenamer
Note: Rename ID to TOID and other attributes to make easier to read
Note: Creates geometry for connecting roadlinks and pathlinks
AttributeRenamer
    ATTR_TABLE:
      RENAME_SET_DEFAULT gml_id > TOID
      RENAME_SET_DEFAULT inspireId.Identifier.localId > identifier
      RENAME_SET_DEFAULT pathNode.xlink_href > pathNode
      RENAME_SET_DEFAULT connectingNode.xlink_href > connectingNode
    -> DateFormatter
DateFormatter
    INVALID_DATE_VALUE = FME_NULL_VALUE
    FMT = FME Date (%Y%m%d)
    DATE_ATTR = beginLifespanVersion
    SRCFMT = Unknown - Automatic Detection
    -> StringReplacer
Note: Remove unwanted #
StringReplacer
    SRC_ATTRS = pathNode,connectingNode
    FIND_TEXT = #
    REGEXP = NO
    NO_MATCH = _FME_NO_OP_
    CASE = NO
    -> ConnectingLink (writer GEOPACKAGE_1)
Note: fictitious set to char (not boolean) so that True or False will appear in the data; / ESRI defaults to 1 or 0 respectively.
Note: change output to prefered format
ConnectingLink (writer GEOPACKAGE_1)
    attributes: TOID text(20), identifier text(37), beginLifespanVersion datetime, reasonForChange text(32), fictitious text(5), connectingNode text(20), pathNode text(20)
