FME workspace AccessRestriction.fmw

Parameters:
- SourceDataset_GML_3 = C:\Temp\Highways_Data\Highways_RoadsAndRAM_AccessRestriction_001.gml.gz   # Source Geography Markup Language (GML) File(s)
- DestDataset_GEOPACKAGE =   # Destination GeoPackage File

Readers:
- GML_1: GML from $(SourceDataset_GML_3)

Writers:
- GEOPACKAGE_1: GEOPACKAGE to $(DestDataset_GEOPACKAGE)

Note: Set input to local GML files
Note: Some transformers are incomplete as the data is not currently present
AccessRestriction (reader GML_1)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NodeReference.element.owns xml_boolean, networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer,
      networkRef{}.LinkReference.applicableDirection.xsi_nil xml_boolean, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean, networkRef{}.SimplePointReference.atPosition xml_real64, networkRef{}.SimplePointReference.atPosition.uom xml_buffer, networkRef{}.SimplePointReference.offset xml_real64, networkRef{}.SimplePointReference.offset.nilReason xml_buffer, networkRef{}.SimplePointReference.offset.uom xml_buffer, networkRef{}.SimplePointReference.offset.xsi_nil xml_boolean, networkRef{}.PointReference.element.owns xml_boolean, networkRef{}.PointReference.element.nilReason xml_buffer, networkRef{}.PointReference.element.gml_remoteSchema xml_buffer, networkRef{}.PointReference.element.xlink_href xml_buffer, networkRef{}.PointReference.applicableDirection.owns xml_boolean, networkRef{}.PointReference.applicableDirection.nilReason xml_buffer, networkRef{}.PointReference.applicableDirection.gml_remoteSchema xml_buffer, networkRef{}.PointReference.applicableDirection.xlink_href xml_buffer, networkRef{}.PointReference.applicableDirection.xsi_nil xml_boolean, networkRef{}.PointReference.atPosition xml_real64, networkRef{}.PointReference.atPosition.uom xml_buffer, networkRef{}.PointReference.offset xml_real64, networkRef{}.PointReference.offset.nilReason xml_buffer, networkRef{}.PointReference.offset.uom xml_buffer,
      networkRef{}.PointReference.offset.xsi_nil xml_boolean, networkRef{}.PointReference.atPositionGeometry xml_geometry, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64, networkRef{}.SimpleLinearReference.offset.nilReason xml_buffer, networkRef{}.SimpleLinearReference.offset.uom xml_buffer, networkRef{}.SimpleLinearReference.offset.xsi_nil xml_boolean, networkRef{}.LinearReference.element.owns xml_boolean, networkRef{}.LinearReference.element.nilReason xml_buffer, networkRef{}.LinearReference.element.gml_remoteSchema xml_buffer, networkRef{}.LinearReference.element.xlink_href xml_buffer, networkRef{}.LinearReference.applicableDirection.owns xml_boolean, networkRef{}.LinearReference.applicableDirection.nilReason xml_buffer, networkRef{}.LinearReference.applicableDirection.gml_remoteSchema xml_buffer, networkRef{}.LinearReference.applicableDirection.xlink_href xml_buffer, networkRef{}.LinearReference.applicableDirection.xsi_nil xml_boolean, networkRef{}.LinearReference.fromPosition xml_real64, networkRef{}.LinearReference.fromPosition.uom xml_buffer,
      networkRef{}.LinearReference.toPosition xml_real64, networkRef{}.LinearReference.toPosition.uom xml_buffer, networkRef{}.LinearReference.offset xml_real64, networkRef{}.LinearReference.offset.nilReason xml_buffer, networkRef{}.LinearReference.offset.uom xml_buffer, networkRef{}.LinearReference.offset.xsi_nil xml_boolean, networkRef{}.LinearReference.fromPositionGeometry xml_geometry, networkRef{}.LinearReference.toPositionGeometry xml_geometry, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, restriction.owns xml_boolean, restriction.nilReason xml_buffer, restriction.gml_remoteSchema xml_buffer, restriction.xlink_href xml_buffer, exemption.VehicleQualifier.use{} xml_char(22),
      exemption.VehicleQualifier.use{}.codeSpace xml_char(57), exemption.VehicleQualifier.vehicle{} xml_char(13), exemption.VehicleQualifier.vehicle{}.codeSpace xml_char(61), inclusion.VehicleQualifier.vehicle{} xml_char(30), inclusion.VehicleQualifier.vehicle{}.codeSpace xml_char(61), reasonForChange xml_char(4), reasonForChange.codeSpace xml_char(47), timeInterval{}.TemporalPropertyType.dayPeriod{}.DayPropertyType.namedDay{} xml_char(9), timeInterval{}.TemporalPropertyType.dayPeriod{}.DayPropertyType.namedDay{}.codeSpace xml_char(53), timeInterval{}.TemporalPropertyType.dayPeriod{}.DayPropertyType.namedPeriod{} xml_char(18), timeInterval{}.TemporalPropertyType.dayPeriod{}.DayPropertyType.namedPeriod{}.codeSpace xml_char(56), timeInterval{}.TemporalPropertyType.dayPeriod{}.DayPropertyType.timePeriod{}.TimePropertyType.timeRange{}.TimeRangeType.endTime xml_char(9), timeInterval{}.TemporalPropertyType.dayPeriod{}.DayPropertyType.timePeriod{}.TimePropertyType.timeRange{}.TimeRangeType.startTime xml_char(9), timeInterval{}.TemporalPropertyType.namedDate{} xml_char(9), timeInterval{}.TemporalPropertyType.namedDate{}.codeSpace xml_char(54), trafficSign xml_char(41)
    -> AttributeRenamer
Note: Rename attributes
AttributeRenamer
    ATTR_LIST = inspireId.Identifier.versionId,versionId,,restriction.xlink_href,restriction,,inspireId.Identifier.localId,localId,,gml_id,TOID,
    -> ListExploder
    -> DateFormatter
    -> ListExploder_4
    -> ListExploder_3
    -> ListExploder_5
    -> ListExploder_2
    -> ListExploder_6
    -> ListExploder_7
    -> ListExploder_8

Bookmark: Create AccessRestriction feature
Note: Format dates to DMY
DateFormatter
    SRCFMT = %Y"-"%m"-"%d"T"%T
    DATE_ATTR = beginLifespanVersion,validFrom
    FMT = FME Date (%Y%m%d)
    INVALID_DATE_VALUE = FME_NULL_VALUE
    -> AttributeSplitter
Note: The attribute value for "restrcition" is held as a / URL therefore to extract the value from the URL / the attribute needs splitting after every "/". This / action will create a list. The values after the last / "/" will contain the attribute value.
AttributeSplitter
    DROP_EMPTY_PARTS = No
    ATTR_NAME = restriction
    DELIMITER = /
    LIST_NAME = _list
    TRIM_OPTION = Both
    -> AttributeRenamer_11
Note: Renaming the last list produced by the / AttributeSplitter which holds the attribute / value for the "restriction" attribute.
AttributeRenamer_11
    ATTR_LIST = _list{5},restriction,
    -> AccessRestriction (writer GEOPACKAGE_1)
Note: This is an example output, writer will need to be added for specific output
AccessRestriction (writer GEOPACKAGE_1)
    attributes: TOID text(20), localId text(37), beginLifespanVersion datetime, restriction text(25), reasonForChange text(20), trafficSign text(120)

Bookmark: Indicates the RoadLink the AccessRestriction references
ListExploder
    ATTR_CONFLICT_RES = Use Original
    LIST_ATTR = networkRef{}
    INDEX_ATTR = _element_index
    ATTR_ACCUM_MODE = Merge Incoming List
    LIST_FOUND -> AttributeRenamer_2
AttributeRenamer_2
    ATTR_LIST = PointReference.element.xlink_href,RoadLink_TOID,
    -> AttributeSplitter_3
Note: The attribute value for "directionality" is held as a / URL therefore to extract the value from the URL / the attribute needs splitting after every "/". This / action will create a list. The values after the last / "/" will contain the attribute value.
AttributeSplitter_3
    DROP_EMPTY_PARTS = No
    ATTR_NAME = PointReference.applicableDirection.xlink_href
    DELIMITER = /
    LIST_NAME = _list
    TRIM_OPTION = Both
    -> AttributeRenamer_10
Note: Renaming the last list produced by the / AttributeSplitter which holds the attribute / value for the "directionality" attribute.
AttributeRenamer_10
    ATTR_LIST = _list{5},applicableDirection,,PointReference.atPosition,atPosition,
    -> StringReplacer
Note: remove # from the / feature references
StringReplacer
    SRC_ATTRS = RoadLink_TOID
    NO_MATCH = _FME_NO_OP_
    CASE = no
    REGEXP = no
    FIND_TEXT = #
    -> AccessRestriction_NetworkRef (writer GEOPACKAGE_1)
Note: Table reference to the RoadLink that the restriction applies to.
AccessRestriction_NetworkRef (writer GEOPACKAGE_1)
    attributes: TOID text(20), RoadLink_TOID text(20), applicableDirection text(120), atPosition double

Bookmark: vehicleQualifer.use values have been exposed
ListExploder_4
    ATTR_CONFLICT_RES = Use Original
    LIST_ATTR = exemption.VehicleQualifier.use{}
    INDEX_ATTR = _element_index
    ATTR_ACCUM_MODE = Merge Incoming List
    LIST_FOUND -> AttributeCreator_2
AttributeCreator_2
    ATTR_LIST = exemptionType,use
    -> AttributeRenamer_4
AttributeRenamer_4
    ATTR_LIST = exemption.VehicleQualifier.use,exemption,
    -> AccessRestriction_Exemption (writer GEOPACKAGE_1)

Bookmark: vehicleQualifer.vehicle values have been exposed
ListExploder_5
    ATTR_CONFLICT_RES = Use Original
    LIST_ATTR = exemption.VehicleQualifier.vehicle{}
    INDEX_ATTR = _element_index
    ATTR_ACCUM_MODE = Merge Incoming List
    LIST_FOUND -> AttributeCreator_3
AttributeCreator_3
    ATTR_LIST = exemptionType,vehicle
    -> AttributeRenamer_3
AttributeRenamer_3
    ATTR_LIST = exemption.VehicleQualifier.vehicle,exemption,
    -> AccessRestriction_Exemption (writer GEOPACKAGE_1)

Bookmark: vehicleQualifer.load values have been exposed
ListExploder_2
    ATTR_CONFLICT_RES = Use Original
    LIST_ATTR = exemption.VehicleQualifier.load{}
    INDEX_ATTR = _element_index
    ATTR_ACCUM_MODE = Merge Incoming List
    LIST_FOUND -> AttributeCreator_4
AttributeCreator_4
    ATTR_LIST = exemptionType,load
    -> AttributeRenamer_5
AttributeRenamer_5
    ATTR_LIST = exemption.VehicleQualifier.load,exemption,
    -> AccessRestriction_Exemption (writer GEOPACKAGE_1)

Bookmark: Identifies the "exemption" "vehicleQualifer" attribute values which apply to any AccessRestriction
Note: The "exemption" attribute is populated by a vehicleQualifer data type. There are 3 attributes which contribute to the vehicleQualifer which are: / 1. Use / 2. Vehicle / 3. Load / Each of these 3 attributes have a multiplicity of 0..* so therefore need to be exposed to ensure all values populate the resulting table. This is carried out by the ListExploder transformer.
AccessRestriction_Exemption (writer GEOPACKAGE_1)
    attributes: TOID text(20), exemption text(50), exemptionType text(10)

Bookmark: vehicleQualifer.use values have been exposed
ListExploder_7
    ATTR_CONFLICT_RES = Use Original
    LIST_ATTR = inclusion.VehicleQualifier.use{}
    INDEX_ATTR = _element_index
    ATTR_ACCUM_MODE = Merge Incoming List
    LIST_FOUND -> AttributeCreator_7
AttributeCreator_7
    ATTR_LIST = inclusionType,use
    -> AttributeRenamer_9
AttributeRenamer_9
    ATTR_LIST = inclusion.VehicleQualifier.use,inclusion,
    -> AccessRestriction_Inclusion (writer GEOPACKAGE_1)

Bookmark: vehicleQualifer.vehicle values have been exposed
ListExploder_3
    ATTR_CONFLICT_RES = Use Original
    LIST_ATTR = inclusion.VehicleQualifier.vehicle{}
    INDEX_ATTR = _element_index
    ATTR_ACCUM_MODE = Merge Incoming List
    LIST_FOUND -> AttributeCreator_5
AttributeCreator_5
    ATTR_LIST = inclusionType,vehicle
    -> AttributeRenamer_7
AttributeRenamer_7
    ATTR_LIST = inclusion.VehicleQualifier.vehicle,inclusion,
    -> AccessRestriction_Inclusion (writer GEOPACKAGE_1)

Bookmark: vehicleQualifer.load values have been exposed
ListExploder_6
    ATTR_CONFLICT_RES = Use Original
    LIST_ATTR = inclusion.VehicleQualifier.load{}
    INDEX_ATTR = _element_index
    ATTR_ACCUM_MODE = Merge Incoming List
    LIST_FOUND -> AttributeCreator_6
AttributeCreator_6
    ATTR_LIST = inclusionType,load
    -> AttributeRenamer_8
AttributeRenamer_8
    ATTR_LIST = inclusion.VehicleQualifier.load,inclusion,
    -> AccessRestriction_Inclusion (writer GEOPACKAGE_1)

Bookmark: Identifies the "inclusion" "vehicleQualifer" attribute values which apply to any AccessRestriction
Note: The "inclusion" attribute is populated by a vehicleQualifer data type. There are 3 attributes which contribute to the vehicleQualifer which are: / 1. Use / 2.Vehicle / 3. Load / Each of these 3 attributes have a multiplicity of 0..* so therefore need to be exposed to ensure all values populate the resulting table. This is carried out by the ListExploder transformer.
AccessRestriction_Inclusion (writer GEOPACKAGE_1)
    attributes: TOID text(20), inclusion text(50), inclusionType text(10)

Bookmark: Time qualifiers
ListExploder_8
    ATTR_CONFLICT_RES = Use Original
    LIST_ATTR = timeInterval{}
    INDEX_ATTR = _element_index
    ATTR_ACCUM_MODE = Merge Incoming List
    LIST_FOUND -> AttributeRenamer_17
AttributeRenamer_17
    ATTR_TABLE = RENAME_SET_DEFAULT TOID > parentFeature_ID
    -> Counter
Note: Creates an identifier for date element
Counter
    CNT_ATTR = timeInterval_ID
    START = 0
    DOMAIN = counter
    SCOPE = Global
    -> ListExploder_9
    -> TQ_Parent_Date_Join (writer GEOPACKAGE_1)
    -> ListExploder_10
    -> ListExploder_11
ListExploder_11
    ATTR_CONFLICT_RES = Use Original
    LIST_ATTR = TemporalPropertyType.dayPeriod{}
    INDEX_ATTR = _element_index
    ATTR_ACCUM_MODE = Merge Incoming List
    LIST_FOUND -> Counter_2
Note: Creates an identifier for day element
Counter_2
    CNT_ATTR = dayPeriod_ID
    START = 0
    DOMAIN = counter
    SCOPE = Global
    -> ListExploder_12
    -> ListExploder_13
    -> ListExploder_14
    -> TQ_Date_Day_Join (writer GEOPACKAGE_1)
ListExploder_14
    ATTR_CONFLICT_RES = Use Original
    LIST_ATTR = DayPropertyType.timePeriod{}
    INDEX_ATTR = _element_index
    ATTR_ACCUM_MODE = Merge Incoming List
    LIST_FOUND -> Counter_3
Note: Creates an identifier for time element
Counter_3
    CNT_ATTR = timePeriod_ID
    START = 0
    DOMAIN = counter
    SCOPE = Global
    -> ListExploder_15
    -> ListExploder_16
    -> TQ_Day_Time_Join (writer GEOPACKAGE_1)

Bookmark: Date element
TQ_Parent_Date_Join (writer GEOPACKAGE_1)
    attributes: parentFeature_ID text(50), timeInterval_ID mediumint

Bookmark: DateRange
ListExploder_9
    ATTR_CONFLICT_RES = Use Original
    LIST_ATTR = TemporalPropertyType.dateRange{}
    INDEX_ATTR = _element_index
    ATTR_ACCUM_MODE = Merge Incoming List
    LIST_FOUND -> AttributeRenamer_6
AttributeRenamer_6
    ATTR_LIST = DateRangeType.startDate,startDate,,DateRangeType.endDate,endDate,,DateRangeType.startMonthDay,startMonthDay,,DateRangeType.endMonthDay,endMonthDay,
    -> DateFormatter_2
DateFormatter_2
    SRCFMT = Unknown - Automatic Detection
    DATE_ATTR = endDate,startDate
    FMT = FME Date (%Y%m%d)
    INVALID_DATE_VALUE = _FME_NO_OP_
    -> TQ_DateRange (writer GEOPACKAGE_1)
TQ_DateRange (writer GEOPACKAGE_1)
    attributes: parentFeature_ID text(50), timeInterval_ID mediumint, startDate datetime, endDate datetime, startMonthDay text(10), endMonthDay text(10)

Bookmark: NamedDate
ListExploder_10
    ATTR_CONFLICT_RES = Use Original
    LIST_ATTR = TemporalPropertyType.namedDate{}
    INDEX_ATTR = _element_index
    ATTR_ACCUM_MODE = Merge Incoming List
    LIST_FOUND -> AttributeRenamer_12
AttributeRenamer_12
    ATTR_LIST = TemporalPropertyType.namedDate,namedDate,
    -> TQ_NamedDate (writer GEOPACKAGE_1)
TQ_NamedDate (writer GEOPACKAGE_1)
    attributes: parentFeature_ID text(50), timeInterval_ID mediumint, namedDate text(20)

Bookmark: Day element
TQ_Date_Day_Join (writer GEOPACKAGE_1)
    attributes: parentFeature_ID text(50), timeInterval_ID mediumint, dayPeriod_ID mediumint

Bookmark: NamedDay
ListExploder_12
    ATTR_CONFLICT_RES = Use Original
    LIST_ATTR = DayPropertyType.namedDay{}
    INDEX_ATTR = _element_index
    ATTR_ACCUM_MODE = Merge Incoming List
    LIST_FOUND -> AttributeRenamer_13
AttributeRenamer_13
    ATTR_LIST = DayPropertyType.namedDay,namedDay,
    -> TQ_NamedDay (writer GEOPACKAGE_1)
TQ_NamedDay (writer GEOPACKAGE_1)
    attributes: parentFeature_ID text(50), timeInterval_ID mediumint, dayPeriod_ID mediumint, namedDay text(50)

Bookmark: NamedPeriod
ListExploder_13
    ATTR_CONFLICT_RES = Use Original
    LIST_ATTR = DayPropertyType.namedPeriod{}
    INDEX_ATTR = _element_index
    ATTR_ACCUM_MODE = Merge Incoming List
    LIST_FOUND -> AttributeRenamer_14
AttributeRenamer_14
    ATTR_LIST = DayPropertyType.namedPeriod,namedPeriod,
    -> TQ_NamedPeriod (writer GEOPACKAGE_1)
TQ_NamedPeriod (writer GEOPACKAGE_1)
    attributes: parentFeature_ID text(50), timeInterval_ID mediumint, dayPeriod_ID mediumint, namedPeriod text(50)

Bookmark: Time element
TQ_Day_Time_Join (writer GEOPACKAGE_1)
    attributes: parentFeature_ID text(50), timeInterval_ID mediumint, dayPeriod_ID mediumint, timePeriod_ID mediumint

Bookmark: TimeRange
ListExploder_15
    ATTR_CONFLICT_RES = Use Original
    LIST_ATTR = TimePropertyType.timeRange{}
    INDEX_ATTR = _element_index
    ATTR_ACCUM_MODE = Merge Incoming List
    LIST_FOUND -> AttributeRenamer_15
AttributeRenamer_15
    ATTR_LIST = TimeRangeType.startTime,startTime,,TimeRangeType.endTime,endTime,
    -> TQ_TimeRange (writer GEOPACKAGE_1)
TQ_TimeRange (writer GEOPACKAGE_1)
    attributes: parentFeature_ID text(50), timeInterval_ID mediumint, dayPeriod_ID mediumint, timePeriod_ID mediumint, startTime text(10), endTime text(10)

Bookmark: NamedTime
ListExploder_16
    ATTR_CONFLICT_RES = Use Original
    LIST_ATTR = TimePropertyType.namedTime{}
    INDEX_ATTR = _element_index
    ATTR_ACCUM_MODE = Merge Incoming List
    LIST_FOUND -> AttributeRenamer_16
AttributeRenamer_16
    ATTR_LIST = TimePropertyType.namedTime,namedTime,
    -> TQ_NamedTime (writer GEOPACKAGE_1)
TQ_NamedTime (writer GEOPACKAGE_1)
    attributes: parentFeature_ID text(50), timeInterval_ID mediumint, dayPeriod_ID mediumint, timePeriod_ID mediumint, namedTime text(50)
