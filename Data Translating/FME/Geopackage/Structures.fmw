FME workspace Structures.fmw

Parameters:
- SourceDataset_GML_3 = C:\Temp\Highways_Data\Highways_RoadsAndRAM_Structure_001.gml.gz   # Source Geography Markup Language (GML) File(s)
- DestDataset_GEOPACKAGE =   # Destination GeoPackage File

Readers:
- GML_1: GML from $(SourceDataset_GML_3)

Writers:
- GEOPACKAGE_1: GEOPACKAGE to $(DestDataset_GEOPACKAGE)

Note: Change to local input
Structure (reader GML_1)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NodeReference.element.owns xml_boolean, networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer,
      networkRef{}.LinkReference.applicableDirection.xsi_nil xml_boolean, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean, networkRef{}.SimplePointReference.atPosition xml_real64, networkRef{}.SimplePointReference.atPosition.uom xml_buffer, networkRef{}.SimplePointReference.offset xml_real64, networkRef{}.SimplePointReference.offset.nilReason xml_buffer, networkRef{}.SimplePointReference.offset.uom xml_buffer, networkRef{}.SimplePointReference.offset.xsi_nil xml_boolean, networkRef{}.PointReference.element.owns xml_boolean, networkRef{}.PointReference.element.nilReason xml_buffer, networkRef{}.PointReference.element.gml_remoteSchema xml_buffer, networkRef{}.PointReference.element.xlink_href xml_buffer, networkRef{}.PointReference.applicableDirection.owns xml_boolean, networkRef{}.PointReference.applicableDirection.nilReason xml_buffer, networkRef{}.PointReference.applicableDirection.gml_remoteSchema xml_buffer, networkRef{}.PointReference.applicableDirection.xlink_href xml_buffer, networkRef{}.PointReference.applicableDirection.xsi_nil xml_boolean, networkRef{}.PointReference.atPosition xml_real64, networkRef{}.PointReference.atPosition.uom xml_buffer, networkRef{}.PointReference.offset xml_real64, networkRef{}.PointReference.offset.nilReason xml_buffer, networkRef{}.PointReference.offset.uom xml_buffer,
      networkRef{}.PointReference.offset.xsi_nil xml_boolean, networkRef{}.PointReference.atPositionGeometry xml_geometry, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64, networkRef{}.SimpleLinearReference.offset.nilReason xml_buffer, networkRef{}.SimpleLinearReference.offset.uom xml_buffer, networkRef{}.SimpleLinearReference.offset.xsi_nil xml_boolean, networkRef{}.LinearReference.element.owns xml_boolean, networkRef{}.LinearReference.element.nilReason xml_buffer, networkRef{}.LinearReference.element.gml_remoteSchema xml_buffer, networkRef{}.LinearReference.element.xlink_href xml_buffer, networkRef{}.LinearReference.applicableDirection.owns xml_boolean, networkRef{}.LinearReference.applicableDirection.nilReason xml_buffer, networkRef{}.LinearReference.applicableDirection.gml_remoteSchema xml_buffer, networkRef{}.LinearReference.applicableDirection.xlink_href xml_buffer, networkRef{}.LinearReference.applicableDirection.xsi_nil xml_boolean, networkRef{}.LinearReference.fromPosition xml_real64, networkRef{}.LinearReference.fromPosition.uom xml_buffer,
      networkRef{}.LinearReference.toPosition xml_real64, networkRef{}.LinearReference.toPosition.uom xml_buffer, networkRef{}.LinearReference.offset xml_real64, networkRef{}.LinearReference.offset.nilReason xml_buffer, networkRef{}.LinearReference.offset.uom xml_buffer, networkRef{}.LinearReference.offset.xsi_nil xml_boolean, networkRef{}.LinearReference.fromPositionGeometry xml_geometry, networkRef{}.LinearReference.toPositionGeometry xml_geometry, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, structure xml_buffer, structure.codeSpace xml_buffer, description xml_buffer, reasonForChange xml_buffer, reasonForChange.codeSpace xml_buffer
    -> AttributeRenamer
Note: Rename attributes
AttributeRenamer
    ATTR_LIST = inspireId.Identifier.namespace,identifierNamespace,,inspireId.Identifier.versionId,versionId,,inspireId.Identifier.localId,localId,,gml_id,TOID,
    -> DateFormatter
    -> ListExploder_2

Bookmark: Create Structure feature
Note: Format as DMY
DateFormatter
    INVALID_DATE_VALUE = FME_NULL_VALUE
    FMT = FME Date (%Y%m%d)
    DATE_ATTR = beginLifespanVersion
    SRCFMT = Unknown - Automatic Detection
    -> Structure (writer GEOPACKAGE_1)
Note: This is an example output, writer will need to be added for specific output
Structure (writer GEOPACKAGE_1)
    attributes: TOID text(20), localId text(37), beginLifespanVersion datetime, structure text(50), description text(120), reasonForChange text(32)

Bookmark: Identifies the RoadLinks and RoadNodes a Structure references
Note: Exploded list of the different / network references used by Structures
ListExploder_2
    ATTR_ACCUM_MODE = Merge Incoming List
    ATTR_CONFLICT_RES = Use Original
    INDEX_ATTR = _element_index
    LIST_ATTR = networkRef{}
    LIST_FOUND -> TestFilter
TestFilter
    TEST_LIST = BOOL_OP,OR,COMPOSITE_TEST,<Unused>,TEST_CLAUSE,"TEST @Value(LinkReference.element.xlink_href) BEGINS_WITH #",LinkReference,BOOL_OP,OR,COMPOSITE_TEST,<Unused>,TEST_CLAUSE,"TEST @Value(PointReference.element.xlink_href) BEGINS_WITH #",PointReference,BOOL_OP,OR,COMPOSITE_TEST,<Unused>,TEST_CLAUSE,"TEST @Value(NodeReference.element.xlink_href) BEGINS_WITH #",NodeReference
    DEFAULT_VALUE = <UNFILTERED>
    LinkReference -> AttributeRenamer_5
    PointReference -> AttributeRenamer_7
    NodeReference -> AttributeRenamer_6
Note: The Structure feature type uses 3 types of Network Referencing: / 1. Link Referencing / 2. Node Referencing / 3. Point Referencing / This section identifies the type of Network Referencing used. / In addition, Node Referencing will reference the RoadLinks they affect. This has been seperated out into a seperate table in this workbench.
Structure_NetworkRef (writer GEOPACKAGE_1)
    attributes: TOID text(20), RoadNode_TOID text(20), RoadLink_TOID text(20), applicableDirection text(50), atPosition double

Bookmark: Structure features which reference the Linear Highway Network through Link Referencing
AttributeRenamer_5
    ATTR_LIST = LinkReference.element.xlink_href,RoadLink_TOID,
    -> AttributeSplitter_2
Note: The attribute value for "directionality" is held as a / URL therefore to extract the value from the URL / the attribute needs splitting after every "/". This / action will create a list. The values after the last / "/" will contain the attribute value.
AttributeSplitter_2
    DELIMITER = /
    LIST_NAME = _list
    TRIM_OPTION = Both
    DROP_EMPTY_PARTS = No
    ATTR_NAME = LinkReference.applicableDirection.xlink_href
    -> AttributeRenamer_3
Note: Renaming the last list produced / by the AttributeSplitter which holds / the attribute value for the / "directionality" attribute.
AttributeRenamer_3
    ATTR_LIST = _list{5},applicableDirection,
    -> StringReplacer_3
Note: remove # from the / feature references
StringReplacer_3
    SRC_ATTRS = RoadLink_TOID
    FIND_TEXT = #
    REGEXP = no
    NO_MATCH = _FME_NO_OP_
    CASE = no
    -> Structure_NetworkRef (writer GEOPACKAGE_1)

Bookmark: Structure features which reference the Linear Highway Network through Point Referencing
AttributeRenamer_7
    ATTR_LIST = PointReference.element.xlink_href,RoadLink_TOID,
    -> AttributeSplitter_3
Note: The attribute value for "directionality" is held as a / URL therefore to extract the value from the URL / the attribute needs splitting after every "/". This / action will create a list. The values after the last / "/" will contain the attribute value.
AttributeSplitter_3
    DELIMITER = /
    LIST_NAME = _list
    TRIM_OPTION = Both
    DROP_EMPTY_PARTS = No
    ATTR_NAME = PointReference.applicableDirection.xlink_href
    -> AttributeRenamer_4
Note: Renaming the last list produced / by the AttributeSplitter which holds / the attribute value for the / "directionality" attribute.
AttributeRenamer_4
    ATTR_LIST = _list{5},applicableDirection,,PointReference.atPosition,atPosition,,PointReference.atPositionGeometry,atPositionGeometry,
    -> StringReplacer_4
Note: remove # from the / feature references
StringReplacer_4
    SRC_ATTRS = RoadLink_TOID
    FIND_TEXT = #
    REGEXP = no
    NO_MATCH = _FME_NO_OP_
    CASE = no
    -> Structure_NetworkRef (writer GEOPACKAGE_1)

Bookmark: Structure features which reference the Linear Highway Network through Node Referencing
AttributeRenamer_6
    ATTR_LIST = NodeReference.element.xlink_href,RoadNode_TOID,
    -> StringReplacer_2
Note: remove # from the / feature references
StringReplacer_2
    SRC_ATTRS = RoadNode_TOID
    FIND_TEXT = #
    REGEXP = no
    NO_MATCH = _FME_NO_OP_
    CASE = no
    -> ListExploder_3
    -> Structure_NetworkRef (writer GEOPACKAGE_1)
Note: Features which use a Node Reference will also reference / the RoadLinks which they impact.Therefore, this list / exploder identifies the RoadLinks the Strucutre feature / affects.
ListExploder_3
    ATTR_ACCUM_MODE = Merge Incoming List
    ATTR_CONFLICT_RES = Use Original
    INDEX_ATTR = _element_index
    LIST_ATTR = NodeReference.linkReference{}
    LIST_FOUND -> AttributeRenamer_2
AttributeRenamer_2
    ATTR_LIST = xlink_href,RoadLink_TOID,
    -> StringReplacer_5
Note: remove # from the / feature references
StringReplacer_5
    SRC_ATTRS = RoadLink_TOID
    FIND_TEXT = #
    REGEXP = no
    NO_MATCH = _FME_NO_OP_
    CASE = no
    -> Structure_NodeReference_LinkReference (writer GEOPACKAGE_1)
Structure_NodeReference_LinkReference (writer GEOPACKAGE_1)
    attributes: TOID text(20), RoadLink_TOID text(20)
