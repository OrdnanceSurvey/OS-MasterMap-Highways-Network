FME workspace Reinstatement.fmw

Parameters:
- SourceDataset_GML_3 = C:\Data\OSMasterMap\Highways\Data\data\Highways_Rrami_Reinstatement_FULL_001.gml.gz   # Source Geography Markup Language (GML) File(s)
- DestDataset_GEOPACKAGE = C:\Data\OSMasterMap\Highways\Data\test.gpkg   # GeoPackage File

Readers:
- GML_1: GML from $(SourceDataset_GML_3)

Writers:
- GEOPACKAGE_1: GEOPACKAGE to $(DestDataset_GEOPACKAGE)

Note: Change to local input
Note: All Reinstatement features will reference back to the Street feature (the USRN) of the Linear Highway Network. A single Reinstatement feature will not reference multiple Street features. The Reinstatement feature has come directly from the NSG. / Reinstatement features may reference a whole Street feature and in this instance no geometry is provided. / A Reinstatement feature may only partially reference the Street feature. In these instances a location description is provided and a start location and end location will be provided where they are within 10m of the network. When geometry is provided both a start location and an end location will be provided which results in the feature having a mult point geometry.
Reinstatement (reader GML_1)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NodeReference.element.owns xml_boolean, networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer,
      networkRef{}.LinkReference.applicableDirection.xsi_nil xml_boolean, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean, networkRef{}.SimplePointReference.atPosition xml_real64, networkRef{}.SimplePointReference.atPosition.uom xml_buffer, networkRef{}.SimplePointReference.offset xml_real64, networkRef{}.SimplePointReference.offset.nilReason xml_buffer, networkRef{}.SimplePointReference.offset.uom xml_buffer, networkRef{}.SimplePointReference.offset.xsi_nil xml_boolean, networkRef{}.PointReference.element.owns xml_boolean, networkRef{}.PointReference.element.nilReason xml_buffer, networkRef{}.PointReference.element.gml_remoteSchema xml_buffer, networkRef{}.PointReference.element.xlink_href xml_buffer, networkRef{}.PointReference.applicableDirection.owns xml_boolean, networkRef{}.PointReference.applicableDirection.nilReason xml_buffer, networkRef{}.PointReference.applicableDirection.gml_remoteSchema xml_buffer, networkRef{}.PointReference.applicableDirection.xlink_href xml_buffer, networkRef{}.PointReference.applicableDirection.xsi_nil xml_boolean, networkRef{}.PointReference.atPosition xml_real64, networkRef{}.PointReference.atPosition.uom xml_buffer, networkRef{}.PointReference.offset xml_real64, networkRef{}.PointReference.offset.nilReason xml_buffer, networkRef{}.PointReference.offset.uom xml_buffer,
      networkRef{}.PointReference.offset.xsi_nil xml_boolean, networkRef{}.PointReference.atPositionGeometry xml_geometry, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64, networkRef{}.SimpleLinearReference.offset.nilReason xml_buffer, networkRef{}.SimpleLinearReference.offset.uom xml_buffer, networkRef{}.SimpleLinearReference.offset.xsi_nil xml_boolean, networkRef{}.LinearReference.element.owns xml_boolean, networkRef{}.LinearReference.element.nilReason xml_buffer, networkRef{}.LinearReference.element.gml_remoteSchema xml_buffer, networkRef{}.LinearReference.element.xlink_href xml_buffer, networkRef{}.LinearReference.applicableDirection.owns xml_boolean, networkRef{}.LinearReference.applicableDirection.nilReason xml_buffer, networkRef{}.LinearReference.applicableDirection.gml_remoteSchema xml_buffer, networkRef{}.LinearReference.applicableDirection.xlink_href xml_buffer, networkRef{}.LinearReference.applicableDirection.xsi_nil xml_boolean, networkRef{}.LinearReference.fromPosition xml_real64, networkRef{}.LinearReference.fromPosition.uom xml_buffer,
      networkRef{}.LinearReference.toPosition xml_real64, networkRef{}.LinearReference.toPosition.uom xml_buffer, networkRef{}.LinearReference.offset xml_real64, networkRef{}.LinearReference.offset.nilReason xml_buffer, networkRef{}.LinearReference.offset.uom xml_buffer, networkRef{}.LinearReference.offset.xsi_nil xml_boolean, networkRef{}.LinearReference.fromPositionGeometry xml_geometry, networkRef{}.LinearReference.toPositionGeometry xml_geometry, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, reinstatementType xml_buffer, reinstatementType.codeSpace xml_buffer, partialReference xml_boolean, reasonForChange xml_buffer, reasonForChange.codeSpace xml_buffer
    -> ListIndexer

Bookmark: Create Reinstatement feature. The network reference is included in this feature output.
Note: Pull out the first network reference, / there will only ever be one.
ListIndexer
    PREFIX = net_ref_
    LIST_ATTR = networkRef{}
    INDEX = 0
    -> AttributeRenamer_2
AttributeRenamer_2
    ATTR_LIST = inspireId.Identifier.localId,localId,,inspireId.Identifier.versionId,versionID,,gml_id,ID,,networkRef{0}.NetworkReference.element.xlink_href,referenceToStreetUSRN,,net_ref_NetworkReferenceLocation.locationEnd,locationEnd,,net_ref_NetworkReferenceLocation.locationStart,locationStart,
    -> DateFormatter
DateFormatter
    SRCFMT = %Y"-"%m"-"%d"T"%T
    FMT = FME Date (%Y%m%d)
    DATE_ATTR = beginLifespanVersion,endLifespanVersion,validFrom,validTo
    INVALID_DATE_VALUE = FME_NULL_VALUE
    -> TestFilter
Note: Identify if the Reinstatement feature partially references the Network. If the result is "True" then the network reference is held in a different attribute and splitting here will enable bringing the Network reference into the same attribute in the final result.
TestFilter
    DEFAULT_VALUE = <UNFILTERED>
    TEST_LIST = BOOL_OP,OR,COMPOSITE_TEST,<Unused>,TEST_CLAUSE,"TEST @Value(partialReference) = false",False,BOOL_OP,OR,COMPOSITE_TEST,<Unused>,TEST_CLAUSE,"TEST @Value(partialReference) = true",True
    False -> AttributeRenamer
    True -> AttributeRenamer_3
AttributeRenamer
    ATTR_LIST = net_ref_NetworkReferenceLocation.locationDescription,locationDescription,,net_ref_NetworkReference.element.xlink_href,referenceToStreetUSRN,
    -> StringReplacer
AttributeRenamer_3
    ATTR_LIST = net_ref_NetworkReferenceLocation.element.xlink_href,referenceToStreetUSRN,,net_ref_NetworkReferenceLocation.locationDescription,locationDescription,
    -> StringReplacer
Note: remove # from the / feature references
StringReplacer
    REGEXP = no
    CASE = no
    SRC_ATTRS = referenceToStreetUSRN
    NO_MATCH = _FME_NO_OP_
    FIND_TEXT = #
    -> GeometryFilter
GeometryFilter
    BREAK_AGG = No
    GEOM_PORT_NAMES = Point Line Area
    POINT -> GeometryRefiner
    LINE -> Reinstatement_line (writer GEOPACKAGE_1)
    AREA -> Reinstatement_area (writer GEOPACKAGE_1)
    <UNFILTERED> -> Reinstatement_noGeom (writer GEOPACKAGE_1)
GeometryRefiner
    -> Reinstatement_point (writer GEOPACKAGE_1)
Reinstatement_point (writer GEOPACKAGE_1)
    attributes: ID text(20), localId text(20), beginLifespanVersion datetime, validFrom datetime, reinstatementType text(120), partialReference text(5), reasonForChange text(32), locationDescription text(120), referenceToStreetUSRN text(20), locationStart text(20), locationEnd text(20)
Reinstatement_line (writer GEOPACKAGE_1)
    attributes: ID text(20), localId text(20), beginLifespanVersion datetime, validFrom datetime, reinstatementType text(120), partialReference text(5), reasonForChange text(32), locationDescription text(120), referenceToStreetUSRN text(20)
Reinstatement_area (writer GEOPACKAGE_1)
    attributes: ID text(20), localId text(20), beginLifespanVersion datetime, validFrom datetime, reinstatementType text(120), partialReference text(5), reasonForChange text(32), locationDescription text(120), referenceToStreetUSRN text(20)
Note: This is an example output, writer will need to be added for specific output
Reinstatement_noGeom (writer GEOPACKAGE_1)
    attributes: ID text(20), localId text(20), beginLifespanVersion datetime, validFrom datetime, reinstatementType text(120), partialReference text(5), reasonForChange text(32), locationDescription text(120), referenceToStreetUSRN text(20)
