FME workspace RestrictionForVehicles.fmw

Parameters:
- SourceDataset_GML = C:\Temp\Highways_Data\Highways_RoadsAndRAM_RestrictionForVehicles_001.gml.gz   # Source Geography Markup Language (GML) File(s)
- DestDataset_GEOPACKAGE =   # Destination GeoPackage File

Readers:
- GML_1: GML from $(SourceDataset_GML)

Writers:
- GEOPACKAGE_1: GEOPACKAGE to $(DestDataset_GEOPACKAGE)

Note: Change to local input
RestrictionForVehicles (reader GML_1)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer, networkRef{}.LinkReference.applicableDirection.xsi_nil xml_boolean, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64, networkRef{}.SimpleLinearReference.offset.nilReason xml_buffer,
      networkRef{}.SimpleLinearReference.offset.uom xml_buffer, networkRef{}.SimpleLinearReference.offset.xsi_nil xml_boolean, networkRef{}.LinearReference.element.owns xml_boolean, networkRef{}.LinearReference.element.nilReason xml_buffer, networkRef{}.LinearReference.element.gml_remoteSchema xml_buffer, networkRef{}.LinearReference.element.xlink_href xml_buffer, networkRef{}.LinearReference.applicableDirection.owns xml_boolean, networkRef{}.LinearReference.applicableDirection.nilReason xml_buffer, networkRef{}.LinearReference.applicableDirection.gml_remoteSchema xml_buffer, networkRef{}.LinearReference.applicableDirection.xlink_href xml_buffer, networkRef{}.LinearReference.applicableDirection.xsi_nil xml_boolean, networkRef{}.LinearReference.fromPosition xml_real64, networkRef{}.LinearReference.fromPosition.uom xml_buffer, networkRef{}.LinearReference.toPosition xml_real64, networkRef{}.LinearReference.toPosition.uom xml_buffer, networkRef{}.LinearReference.offset xml_real64, networkRef{}.LinearReference.offset.nilReason xml_buffer, networkRef{}.LinearReference.offset.uom xml_buffer, networkRef{}.LinearReference.offset.xsi_nil xml_boolean, networkRef{}.LinearReference.fromPositionGeometry xml_geometry, networkRef{}.LinearReference.toPositionGeometry xml_geometry, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean,
      networkRef{}.SimplePointReference.atPosition xml_real64, networkRef{}.SimplePointReference.atPosition.uom xml_buffer, networkRef{}.SimplePointReference.offset xml_real64, networkRef{}.SimplePointReference.offset.nilReason xml_buffer, networkRef{}.SimplePointReference.offset.uom xml_buffer, networkRef{}.SimplePointReference.offset.xsi_nil xml_boolean, networkRef{}.PointReference.element.owns xml_boolean, networkRef{}.PointReference.element.nilReason xml_buffer, networkRef{}.PointReference.element.gml_remoteSchema xml_buffer, networkRef{}.PointReference.element.xlink_href xml_buffer, networkRef{}.PointReference.applicableDirection.owns xml_boolean, networkRef{}.PointReference.applicableDirection.nilReason xml_buffer, networkRef{}.PointReference.applicableDirection.gml_remoteSchema xml_buffer, networkRef{}.PointReference.applicableDirection.xlink_href xml_buffer, networkRef{}.PointReference.applicableDirection.xsi_nil xml_boolean, networkRef{}.PointReference.atPosition xml_real64, networkRef{}.PointReference.atPosition.uom xml_buffer, networkRef{}.PointReference.offset xml_real64, networkRef{}.PointReference.offset.nilReason xml_buffer, networkRef{}.PointReference.offset.uom xml_buffer, networkRef{}.PointReference.offset.xsi_nil xml_boolean, networkRef{}.PointReference.atPositionGeometry xml_geometry, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NodeReference.element.owns xml_boolean,
      networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, measure xml_real64, measure.uom xml_buffer, restrictionType.owns xml_boolean, restrictionType.nilReason xml_buffer, restrictionType.gml_remoteSchema xml_buffer,
      restrictionType.xlink_href xml_buffer, exemption.VehicleQualifier.use{} xml_char(7), exemption.VehicleQualifier.use{}.codeSpace xml_char(57), measure2 xml_decimal(4,0), measure2.uom xml_char(3), reasonForChange xml_char(33), reasonForChange.codeSpace xml_char(51), sourceOfMeasure xml_char(11), structure xml_char(18), structure.codeSpace xml_char(63), trafficSign{} xml_char(75)
    -> AttributeRenamer
Note: There are currently no vehicle qualifiers of vehicle or load, as a result FME cannot find the attributes, the ListExploder's have been disabled
Note: Rename attributes
AttributeRenamer
    ATTR_LIST = inspireId.Identifier.localId,identifier,,inspireId.Identifier.versionId,versionId,,measure.uom,measure_uom,,measure2.uom,measure2_uom,,locationDescripton,locationDescription,,locationDescripton.xml_lang,locationDescription_lang,,trafficRegulationOrder.TrafficRegulationOrderType.trafficRegulationOrder,trafficRegulationOrder,,trafficRegulationOrder.TrafficRegulationOrderType.troDescription,troDescription,,gml_id,TOID,
    -> DateFormatter
    -> ListExploder
    -> ListExploder_3 [off]
    -> ListExploder_2 [off]
    -> ListExploder_4 [off]
    -> ListExploder_5 [off]
    -> ListExploder_7 [off]
    -> ListExploder_6 [off]

Bookmark: Create RestrictionForVehicles feature
Note: Format dates as DMY
Note: Split traffic signals into 2 attributes as the multiplicity is 1..2.
DateFormatter
    INVALID_DATE_VALUE = FME_NULL_VALUE
    FMT = FME Date (%Y%m%d)
    DATE_ATTR = beginLifespanVersion,validFrom
    SRCFMT = Unknown - Automatic Detection
    -> ListIndexer
Note: The attribute value for "restrcitionType" is held as a / URL therefore to extract the value from the URL / the attribute needs splitting after every "/". This / action will create a list. The values after the last / "/" will contain the attribute value.
AttributeSplitter
    DELIMITER = /
    LIST_NAME = _list
    TRIM_OPTION = Both
    DROP_EMPTY_PARTS = No
    ATTR_NAME = restrictionType.xlink_href
    -> AttributeRenamer_11
Note: Renaming the last list produced by the / AttributeSplitter which holds the attribute / value for the "restrictionType" attribute.
AttributeRenamer_11
    ATTR_LIST = _list{5},restrictionType,
    -> RestrictionForVehicles (writer GEOPACKAGE_1)
Note: This is an example output, writer will need to be added for specific output
RestrictionForVehicles (writer GEOPACKAGE_1)
    attributes: TOID text(20), identifier text(37), beginLifespanVersion datetime, reasonForChange text(20), restrictionType text(20), measure double, measure_uom text(20), sourceOfMeasure text(32), measure2 double, measure2_uom text(20), structure text(32), trafficSign1 text(120), trafficSign2 text(120), trafficRegulationOrder text(120), troDescription text(20)

Bookmark: Traffic Sign 1
ListIndexer
    PREFIX = trafficSign1_
    INDEX = 0
    LIST_ATTR = trafficSign{}
    -> AttributeRenamer_2
AttributeRenamer_2
    ATTR_LIST = trafficSign1_trafficSign,trafficSign1,
    -> ListIndexer_2

Bookmark: Traffic Sign 2
ListIndexer_2
    PREFIX = trafficSign2_
    INDEX = 1
    LIST_ATTR = trafficSign{}
    -> AttributeRenamer_3
AttributeRenamer_3
    ATTR_LIST = trafficSign2_trafficSign,trafficSign2,
    -> AttributeSplitter

Bookmark: vehicleQualifer.use values have been exposed
ListExploder_3
    ATTR_ACCUM_MODE = Merge Incoming List
    ATTR_CONFLICT_RES = Use Original
    INDEX_ATTR = _element_index
    LIST_ATTR = exemption.VehicleQualifier.use{}
    LIST_FOUND -> AttributeCreator_2
AttributeCreator_2
    ATTR_LIST = exemptionType,use
    -> AttributeRenamer_5
AttributeRenamer_5
    ATTR_LIST = ExemptionType.use,exemption,
    -> RestrictionForVehicles_Exemption (writer GEOPACKAGE_1)

Bookmark: vehicleQualifer.vehicle values have been exposed
ListExploder_4 [off]
    ATTR_ACCUM_MODE = Merge Incoming List
    ATTR_CONFLICT_RES = Use Original
    INDEX_ATTR = _element_index
    LIST_ATTR = exemption.VehicleQualifier.vehicle{}
    LIST_FOUND -> AttributeCreator_3
AttributeCreator_3
    ATTR_LIST = exemptionType,vehicle
    -> AttributeRenamer_6
AttributeRenamer_6
    ATTR_LIST = ExemptionType.vehicle,exemption,
    -> RestrictionForVehicles_Exemption (writer GEOPACKAGE_1)

Bookmark: vehicleQualifer.load values have been exposed
ListExploder_2 [off]
    ATTR_ACCUM_MODE = Merge Incoming List
    ATTR_CONFLICT_RES = Use Original
    INDEX_ATTR = _element_index
    LIST_ATTR = exemption.VehicleQualifier.load{}
    LIST_FOUND -> AttributeCreator
AttributeCreator
    ATTR_LIST = exemptionType,load
    -> AttributeRenamer_4
AttributeRenamer_4
    ATTR_LIST = ExemptionType.load,exemption,
    -> RestrictionForVehicles_Exemption (writer GEOPACKAGE_1)

Bookmark: Identifies the "exemption" "vehicleQualifer" attribute values which apply to any RestrictionForVehicles - Disabled
Note: The "exemption" attribute is populated by a vehicleQualifer data type. There are 3 attributes which contribute to the vehicleQualifer which are: / 1. Use / 2.Vehicle / 3. Load / Each of these 3 attributes have a multiplicity of 0..* so therefore need to be exposed to ensure all values populate the resulting table. This is carried out by the ListExploder transformer. / The link to this process has been disabled as there are currently no expemtions available in the product for RestrictionForVehicle features.
RestrictionForVehicles_Exemption (writer GEOPACKAGE_1)
    attributes: TOID text(20), exemption text(50), exemptionType text(10)

Bookmark: vehicleQualifer.use values have been exposed
ListExploder_7
    ATTR_ACCUM_MODE = Merge Incoming List
    ATTR_CONFLICT_RES = Use Original
    INDEX_ATTR = _element_index
    LIST_ATTR = exemption.VehicleQualifier.use{}
    LIST_FOUND -> AttributeCreator_7
AttributeCreator_7
    ATTR_LIST = inclusionType,use
    -> AttributeRenamer_10
AttributeRenamer_10
    ATTR_LIST = inclusion.VehicleQualifier.use,inclusion,
    -> RestrictionForVehicles_Inclusion (writer GEOPACKAGE_1)

Bookmark: vehicleQualifer.vehicle values have been exposed
ListExploder_5 [off]
    ATTR_ACCUM_MODE = Merge Incoming List
    ATTR_CONFLICT_RES = Use Original
    INDEX_ATTR = _element_index
    LIST_ATTR = inclusion.VehicleQualifier.vehicle{}
    LIST_FOUND -> AttributeCreator_5
AttributeCreator_5
    ATTR_LIST = inclusionType,vehicle
    -> AttributeRenamer_8
AttributeRenamer_8
    ATTR_LIST = inclusion.VehicleQualifier.vehicle,inclusion,
    -> RestrictionForVehicles_Inclusion (writer GEOPACKAGE_1)

Bookmark: vehicleQualifer.load values have been exposed
ListExploder_6 [off]
    ATTR_ACCUM_MODE = Merge Incoming List
    ATTR_CONFLICT_RES = Use Original
    INDEX_ATTR = _element_index
    LIST_ATTR = inclusion.VehicleQualifier.load{}
    LIST_FOUND -> AttributeCreator_6
AttributeCreator_6
    ATTR_LIST = inclusionType,load
    -> AttributeRenamer_9
AttributeRenamer_9
    ATTR_LIST = inclusion.VehicleQualifier.load,inclusion,
    -> RestrictionForVehicles_Inclusion (writer GEOPACKAGE_1)

Bookmark: Identifies the "inclusion" "vehicleQualifer" attribute values which apply to any RestrictionForVehicle - Disabled
Note: The "exemption" attribute is populated by a vehicleQualifer data type. There are 3 attributes which contribute to the vehicleQualifer which are: / 1. Use / 2.Vehicle / 3. Load / Each of these 3 attributes have a multiplicity of 0..* so therefore need to be exposed to ensure all values populate the resulting table. This is carried out by the ListExploder transformer. / The link to this process has been disabled as there are currently no expemtions available in the product for RestrictionForVehicle features.
RestrictionForVehicles_Inclusion (writer GEOPACKAGE_1)
    attributes: TOID text(20), inclusion text(50), inclusionType text(10)

Bookmark: Identifies the RoadLinks and RoadNodes a RestrictionForVehicle references
ListExploder
    ATTR_ACCUM_MODE = Merge Incoming List
    ATTR_CONFLICT_RES = Use Original
    INDEX_ATTR = _element_index
    LIST_ATTR = networkRef{}
    LIST_FOUND -> TestFilter
TestFilter
    TEST_LIST = BOOL_OP,OR,COMPOSITE_TEST,<Unused>,TEST_CLAUSE,"TEST @Value(PointReference.element.xlink_href) BEGINS_WITH #",PointReference,BOOL_OP,OR,COMPOSITE_TEST,<Unused>,TEST_CLAUSE,"TEST @Value(NodeReference.element.xlink_href) BEGINS_WITH #",NodeReference
    DEFAULT_VALUE = <UNFILTERED>
    PointReference -> AttributeRenamer_12
    NodeReference -> AttributeRenamer_7
Note: The RestrictionForVehicle feature type uses 2 types of Network Referencing: / 1. Node Referencing / 2. Point Referencing / This section identifies the type of Network Referencing used. / In addition, Node Referencing will reference the RoadLinks they affect. This has been seperated out into a seperate table in this workbench.
RestrictionForVehicles_NetworkRef (writer GEOPACKAGE_1)
    attributes: TOID text(20), RoadNode_TOID text(20), RoadLink_TOID text(20), applicableDirection text(120), atPosition double

Bookmark: RestrictionForVehicle features which reference the Linear Highway Network through Point Referencing
AttributeRenamer_12
    ATTR_LIST = PointReference.element.xlink_href,RoadLink_TOID,
    -> AttributeSplitter_2
Note: The attribute value for "directionality" is held as a / URL therefore to extract the value from the URL / the attribute needs splitting after every "/". This / action will create a list. The values after the last / "/" will contain the attribute value.
AttributeSplitter_2
    DELIMITER = /
    LIST_NAME = _list
    TRIM_OPTION = Both
    DROP_EMPTY_PARTS = No
    ATTR_NAME = PointReference.applicableDirection.xlink_href
    -> AttributeRenamer_13
Note: Renaming the last list produced / by the AttributeSplitter which holds / the attribute value for the / "directionality" attribute.
AttributeRenamer_13
    ATTR_LIST = _list{5},applicableDirection,,PointReference.atPosition,atPosition,,PointReference.atPositionGeometry,atPositionGeometry,
    -> StringReplacer_2
Note: remove # from the / feature references
StringReplacer_2
    SRC_ATTRS = RoadLink_TOID
    FIND_TEXT = #
    REGEXP = no
    NO_MATCH = _FME_NO_OP_
    CASE = no
    -> RestrictionForVehicles_NetworkRef (writer GEOPACKAGE_1)

Bookmark: RestrictionForVehicle features which reference the Linear Highway Network through Node Referencing
AttributeRenamer_7
    ATTR_LIST = NodeReference.element.xlink_href,RoadNode_TOID,
    -> StringReplacer
Note: remove # from the / feature references
StringReplacer
    SRC_ATTRS = RoadNode_TOID
    FIND_TEXT = #
    REGEXP = no
    NO_MATCH = _FME_NO_OP_
    CASE = no
    -> ListExploder_8
    -> RestrictionForVehicles_NetworkRef (writer GEOPACKAGE_1)
Note: Features which use a Node Reference will also reference / the RoadLinks which they impact.Therefore, this list / exploder identifies the RoadLinks the RestrictionForVehicle / feature affects.
ListExploder_8
    ATTR_ACCUM_MODE = Merge Incoming List
    ATTR_CONFLICT_RES = Use Original
    INDEX_ATTR = _element_index
    LIST_ATTR = NodeReference.linkReference{}
    LIST_FOUND -> AttributeRenamer_14
AttributeRenamer_14
    ATTR_LIST = xlink_href,RoadLink_TOID,
    -> StringReplacer_4
Note: remove # from the / feature references
StringReplacer_4
    SRC_ATTRS = RoadLink_TOID
    FIND_TEXT = #
    REGEXP = no
    NO_MATCH = _FME_NO_OP_
    CASE = no
    -> RestrictionForVehicles_NodeReference_LinkReference (writer GEOPACKAGE_1)
RestrictionForVehicles_NodeReference_LinkReference (writer GEOPACKAGE_1)
    attributes: TOID text(20), RoadLink_TOID text(20)
