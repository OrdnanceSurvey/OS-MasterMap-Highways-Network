FME workspace FerryTerminal.fmw

Parameters:
- SourceDataset_GML_3 = C:\Temp\Highways_Data\Paths\Bedford_FerryTerminal.gml.gz   # Source Geography Markup Language (GML) File(s)
- DestDataset_GEOPACKAGE =   # Destination GeoPackage File

Readers:
- GML_1: GML from $(SourceDataset_GML_3)

Writers:
- GEOPACKAGE_1: GEOPACKAGE to $(DestDataset_GEOPACKAGE)

Note: Set input to local GML files
FerryTerminal (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xsi_nil xml_boolean, type.owns xml_boolean, type.nilReason xml_buffer, type.gml_remoteSchema xml_buffer, type.xlink_href xml_buffer, type.xsi_nil xml_boolean, element{}.owns xml_boolean, element{}.nilReason xml_buffer, element{}.gml_remoteSchema xml_buffer, element{}.xlink_href xml_buffer, ferryTerminalName{} xml_buffer, ferryTerminalName{}.xml_lang xml_buffer, ferryTerminalCode xml_buffer, reasonForChange xml_buffer, reasonForChange.codeSpace xml_buffer,
      refToFunctionalSite.nilReason xml_buffer, refToFunctionalSite.gml_remoteSchema xml_buffer, refToFunctionalSite.xlink_href xml_buffer, refToFunctionalSite.owns xml_boolean
    -> AttributeRenamer
Note: Rename ferry name attributes creating name 1 and 2
AttributeRenamer
    ATTR_TABLE:
      RENAME_SET_DEFAULT gml_id > TOID
      RENAME_SET_DEFAULT inspireId.Identifier.localId > identifier
      RENAME_SET_DEFAULT element{0}.xlink_href > ferryNodeRef
      RENAME_SET_DEFAULT element{1}.xlink_href > roadNodeRef
      RENAME_SET_DEFAULT refToFunctionalSite.xlink_href > refToFunctionalSite
      RENAME_SET_DEFAULT type.xlink_href > type
    -> ListIndexer
DateFormatter
    INVALID_DATE_VALUE = FME_NULL_VALUE
    FMT = FME Date (%Y%m%d)
    DATE_ATTR = beginLifespanVersion
    SRCFMT = Unknown - Automatic Detection
    -> StringReplacer
Note: Remove unwanted #
StringReplacer
    NO_MATCH = _FME_NO_OP_
    REGEXP = NO
    CASE = NO
    FIND_TEXT = #
    SRC_ATTRS = type,TOID,refToFunctionalSite
    -> StringReplacer_2
StringReplacer_2
    NO_MATCH = _FME_NO_OP_
    REGEXP = NO
    CASE = NO
    FIND_TEXT = http://inspire.ec.europa.eu/codelist/ConnectionTypeValue/
    SRC_ATTRS = type
    -> FerryTerminal (writer GEOPACKAGE_1)
Note: Change output to prefered format
FerryTerminal (writer GEOPACKAGE_1)
    attributes: TOID text(20), identifier text(37), beginLifespanVersion datetime, type text(10), ferryTerminalName1_text text(120), ferryTerminalName1_lang text(3), ferryTerminalName2_text text(120), ferryTerminalName2_lang text(3), ferryTerminalCode text(10), reasonForChange text(32), ferryNodeRef text(20), roadNodeRef text(20), refToFunctionalSite text(20)

Bookmark: Extract multiple names
ListIndexer
    INDEX = 0
    LIST_ATTR = ferryTerminalName{}
    PREFIX = Name1_
    -> AttributeRenamer_2
AttributeRenamer_2
    ATTR_TABLE:
      RENAME_SET_DEFAULT Name1_ferryTerminalName > ferryTerminalName1_text
      RENAME_SET_DEFAULT Name1_xml_lang > ferryTerminalName1_lang
    -> ListIndexer_2
ListIndexer_2
    INDEX = 1
    LIST_ATTR = ferryTerminalName{}
    PREFIX = Name2_
    -> AttributeRenamer_3
AttributeRenamer_3
    ATTR_TABLE:
      RENAME_SET_DEFAULT Name2_ferryTerminalName > ferryTerminalName2_text
      RENAME_SET_DEFAULT Name2_xml_lang > ferryTerminalName2_lang
    -> DateFormatter
