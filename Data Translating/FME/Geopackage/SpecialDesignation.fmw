FME workspace SpecialDesignation.fmw

Parameters:
- SourceDataset_GML = \\wp149\Product_Archive\OS_MasterMap_Highways_Network\2017\September\RAM\data\Highways_Rrami_SpecialDesignation_FULL_001.gml.gz   # Source Geography Markup Language (GML) File(s)
- DestDataset_GEOPACKAGE = $(FME_MF_DIR)specialdes.gpkg   # Destination GeoPackage File
- DestDataset_GEOPACKAGE_3 =   # GeoPackage File

Readers:
- GML_1: GML from $(SourceDataset_GML)

Writers:
- GEOPACKAGE_1: GEOPACKAGE to $(DestDataset_GEOPACKAGE)
- GEOPACKAGE_2: GEOPACKAGE to $(DestDataset_GEOPACKAGE_3)

Note: Change to local input
SpecialDesignation (reader GML_1)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer, networkRef{}.LinkReference.applicableDirection.xsi_nil xml_boolean, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64, networkRef{}.SimpleLinearReference.offset.nilReason xml_buffer,
      networkRef{}.SimpleLinearReference.offset.uom xml_buffer, networkRef{}.SimpleLinearReference.offset.xsi_nil xml_boolean, networkRef{}.LinearReference.element.owns xml_boolean, networkRef{}.LinearReference.element.nilReason xml_buffer, networkRef{}.LinearReference.element.gml_remoteSchema xml_buffer, networkRef{}.LinearReference.element.xlink_href xml_buffer, networkRef{}.LinearReference.applicableDirection.owns xml_boolean, networkRef{}.LinearReference.applicableDirection.nilReason xml_buffer, networkRef{}.LinearReference.applicableDirection.gml_remoteSchema xml_buffer, networkRef{}.LinearReference.applicableDirection.xlink_href xml_buffer, networkRef{}.LinearReference.applicableDirection.xsi_nil xml_boolean, networkRef{}.LinearReference.fromPosition xml_real64, networkRef{}.LinearReference.fromPosition.uom xml_buffer, networkRef{}.LinearReference.toPosition xml_real64, networkRef{}.LinearReference.toPosition.uom xml_buffer, networkRef{}.LinearReference.offset xml_real64, networkRef{}.LinearReference.offset.nilReason xml_buffer, networkRef{}.LinearReference.offset.uom xml_buffer, networkRef{}.LinearReference.offset.xsi_nil xml_boolean, networkRef{}.LinearReference.fromPositionGeometry xml_geometry, networkRef{}.LinearReference.toPositionGeometry xml_geometry, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean,
      networkRef{}.SimplePointReference.atPosition xml_real64, networkRef{}.SimplePointReference.atPosition.uom xml_buffer, networkRef{}.SimplePointReference.offset xml_real64, networkRef{}.SimplePointReference.offset.nilReason xml_buffer, networkRef{}.SimplePointReference.offset.uom xml_buffer, networkRef{}.SimplePointReference.offset.xsi_nil xml_boolean, networkRef{}.PointReference.element.owns xml_boolean, networkRef{}.PointReference.element.nilReason xml_buffer, networkRef{}.PointReference.element.gml_remoteSchema xml_buffer, networkRef{}.PointReference.element.xlink_href xml_buffer, networkRef{}.PointReference.applicableDirection.owns xml_boolean, networkRef{}.PointReference.applicableDirection.nilReason xml_buffer, networkRef{}.PointReference.applicableDirection.gml_remoteSchema xml_buffer, networkRef{}.PointReference.applicableDirection.xlink_href xml_buffer, networkRef{}.PointReference.applicableDirection.xsi_nil xml_boolean, networkRef{}.PointReference.atPosition xml_real64, networkRef{}.PointReference.atPosition.uom xml_buffer, networkRef{}.PointReference.offset xml_real64, networkRef{}.PointReference.offset.nilReason xml_buffer, networkRef{}.PointReference.offset.uom xml_buffer, networkRef{}.PointReference.offset.xsi_nil xml_boolean, networkRef{}.PointReference.atPositionGeometry xml_geometry, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NodeReference.element.owns xml_boolean,
      networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, designation xml_buffer, designation.codeSpace xml_buffer, description xml_buffer, timeInterval{}.TemporalPropertyType.namedDate{} xml_buffer, timeInterval{}.TemporalPropertyType.namedDate{}.codeSpace xml_buffer,
      timeInterval{}.TemporalPropertyType.dateRange{}.DateRangeType.startDate xml_date, timeInterval{}.TemporalPropertyType.dateRange{}.DateRangeType.endDate xml_date, timeInterval{}.TemporalPropertyType.dateRange{}.DateRangeType.startMonthDay xml_buffer, timeInterval{}.TemporalPropertyType.dateRange{}.DateRangeType.endMonthDay xml_buffer, timeInterval{}.TemporalPropertyType.dayPeriod{}.DayPropertyType.namedDay{} xml_buffer, timeInterval{}.TemporalPropertyType.dayPeriod{}.DayPropertyType.namedDay{}.codeSpace xml_buffer, timeInterval{}.TemporalPropertyType.dayPeriod{}.DayPropertyType.namedPeriod{} xml_buffer, timeInterval{}.TemporalPropertyType.dayPeriod{}.DayPropertyType.namedPeriod{}.codeSpace xml_buffer, timeInterval{}.TemporalPropertyType.dayPeriod{}.DayPropertyType.timePeriod{}.TimePropertyType.namedTime{} xml_buffer, timeInterval{}.TemporalPropertyType.dayPeriod{}.DayPropertyType.timePeriod{}.TimePropertyType.namedTime{}.codeSpace xml_buffer, timeInterval{}.TemporalPropertyType.dayPeriod{}.DayPropertyType.timePeriod{}.TimePropertyType.timeRange{}.TimeRangeType.startTime xml_time, timeInterval{}.TemporalPropertyType.dayPeriod{}.DayPropertyType.timePeriod{}.TimePropertyType.timeRange{}.TimeRangeType.endTime xml_time, contactAuthority.ResponsibleAuthority.identifier xml_buffer, contactAuthority.ResponsibleAuthority.authorityName xml_buffer, partialReference xml_boolean, reasonForChange xml_buffer, reasonForChange.codeSpace xml_buffer
    -> AttributeRenamer
AttributeRenamer
    ATTR_TABLE:
      RENAME_SET_DEFAULT gml_id > id
      RENAME_SET_DEFAULT inspireId.Identifier.localId > identifier
      RENAME_SET_DEFAULT timeInterval.TemporalPropertyType.dateRange.DateRangeType.startDate > startDate
      RENAME_SET_DEFAULT timeInterval.TemporalPropertyType.dateRange.DateRangeType.endDate > endDate
      RENAME_SET_DEFAULT timeInterval.TemporalPropertyType.dayPeriod.DayPropertyType.namedDay > namedDay
      RENAME_SET_DEFAULT timeInterval.TemporalPropertyType.dayPeriod.DayPropertyType.timePeriod.TimePropertyType.timeRange.TimeRangeType.startTime > startTime
      RENAME_SET_DEFAULT timeInterval.TemporalPropertyType.dayPeriod.DayPropertyType.timePeriod.TimePropertyType.timeRange.TimeRangeType.endTime > endTime
      RENAME_SET_DEFAULT validFrom.nilReason > validFrom
    -> ListExploder_10
    -> ListExploder
ListExploder_10
    ATTR_CONFLICT_RES = Use Original
    ATTR_ACCUM_MODE = Merge Incoming List
    LIST_ATTR = networkRef{}
    INDEX_ATTR = _element_index
    LIST_FOUND -> DateFormatter

Bookmark: SpecialDesignation
DateFormatter
    SRCFMT = Unknown - Automatic Detection
    FMT = FME Date (%Y%m%d)
    DATE_ATTR = endLifespanVersion,beginLifespanVersion
    INVALID_DATE_VALUE = FME_NULL_VALUE
    -> TestFilter
TestFilter
    DEFAULT_VALUE = <UNFILTERED>
    TEST_LIST = BOOL_OP,OR,COMPOSITE_TEST,<Unused>,TEST_CLAUSE,"TEST @Value(partialReference) = false",False,BOOL_OP,OR,COMPOSITE_TEST,<Unused>,TEST_CLAUSE,"TEST @Value(partialReference) = true",True
    False -> AttributeRenamer_2
    True -> AttributeRenamer_10
Note: These transformers are where the two different network references get populated into networkRef
AttributeRenamer_2
    ATTR_TABLE:
      RENAME_SET_DEFAULT NetworkReference.element.xlink_href > networkRef
      RENAME_SET_DEFAULT NetworkReferenceLocation.locationEnd > locationEnd
      RENAME_SET_DEFAULT NetworkReferenceLocation.locationStart > locaitonStart
    -> StringReplacer_2
AttributeRenamer_10
    ATTR_TABLE = RENAME_SET_DEFAULT NetworkReferenceLocation.element.xlink_href > networkRef
    -> StringReplacer_2
StringReplacer_2
    REGEXP = NO
    CASE = NO
    SRC_ATTRS = networkRef
    NO_MATCH = _FME_NO_OP_
    FIND_TEXT = #
    -> GeometryFilter
GeometryFilter
    BREAK_AGG = No
    GEOM_PORT_NAMES = Point Line Area
    POINT -> GeometryRefiner
    LINE -> SpecialDesignation_line (writer GEOPACKAGE_2)
    AREA -> SpecialDesignation_area (writer GEOPACKAGE_2)
    <UNFILTERED> -> SpecialDesignation_noGeom (writer GEOPACKAGE_2)
GeometryRefiner
    -> SpecialDesignation_point (writer GEOPACKAGE_2)
SpecialDesignation_point (writer GEOPACKAGE_2)
    attributes: id text(17), identifier text(35), beginLifespanVersion datetime, networkRef text(20), validFrom datetime, validTo datetime, designation text(61), description text(250), contactAuthority text(32), partialReference boolean, reasonForChange text(32), locaitonStart text(32), locationEnd text(32)
SpecialDesignation_line (writer GEOPACKAGE_2)
    attributes: id text(17), identifier text(35), beginLifespanVersion datetime, networkRef text(20), validFrom datetime, validTo datetime, designation text(61), description text(250), contactAuthority text(32), partialReference boolean, reasonForChange text(32)
SpecialDesignation_area (writer GEOPACKAGE_2)
    attributes: id text(17), identifier text(35), beginLifespanVersion datetime, networkRef text(20), validFrom datetime, validTo datetime, designation text(61), description text(250), contactAuthority text(32), partialReference boolean, reasonForChange text(32)
SpecialDesignation_noGeom (writer GEOPACKAGE_2)
    attributes: id text(17), identifier text(35), beginLifespanVersion datetime, networkRef text(20), validFrom datetime, validTo datetime, designation text(61), description text(250), contactAuthority text(32), partialReference boolean, reasonForChange text(32)

Bookmark: Time qualifiers
ListExploder [off]
    ATTR_CONFLICT_RES = Use Original
    ATTR_ACCUM_MODE = Merge Incoming List
    LIST_ATTR = timeInterval{}
    INDEX_ATTR = _element_index
    LIST_FOUND -> AttributeRenamer_3
AttributeRenamer_3 [off]
    ATTR_TABLE = RENAME_SET_DEFAULT id > parentFeature_ID
    -> Counter
Note: Creates an identifier for date element
Counter [off]
    DOMAIN = counter
    START = 0
    SCOPE = Global
    CNT_ATTR = timeInterval_ID
    -> ListExploder_2
    -> ListExploder_3
    -> ListExploder_4
    -> TQ_Parent_Date_Join (writer GEOPACKAGE_2)
ListExploder_4 [off]
    ATTR_CONFLICT_RES = Use Original
    ATTR_ACCUM_MODE = Merge Incoming List
    LIST_ATTR = TemporalPropertyType.dayPeriod{}
    INDEX_ATTR = _element_index
    LIST_FOUND -> Counter_2
Note: Creates an identifier for day element
Counter_2 [off]
    DOMAIN = counter
    START = 0
    SCOPE = Global
    CNT_ATTR = dayPeriod_ID
    -> ListExploder_5
    -> ListExploder_6
    -> ListExploder_7
ListExploder_7 [off]
    ATTR_CONFLICT_RES = Use Original
    ATTR_ACCUM_MODE = Merge Incoming List
    LIST_ATTR = DayPropertyType.timePeriod{}
    INDEX_ATTR = _element_index
    LIST_FOUND -> Counter_3
Note: Creates an identifier for time element
Counter_3 [off]
    DOMAIN = counter
    START = 0
    SCOPE = Global
    CNT_ATTR = timePeriod_ID
    -> ListExploder_8
    -> ListExploder_9
    -> TQ_Day_Time_Join (writer GEOPACKAGE_2)

Bookmark: Date element
TQ_Parent_Date_Join (writer GEOPACKAGE_2)
    attributes: parentFeature_ID text(50), timeInterval_ID mediumint

Bookmark: DateRange
ListExploder_2 [off]
    ATTR_CONFLICT_RES = Use Original
    ATTR_ACCUM_MODE = Merge Incoming List
    LIST_ATTR = TemporalPropertyType.dateRange{}
    INDEX_ATTR = _element_index
    LIST_FOUND -> AttributeRenamer_4 [off]
AttributeRenamer_4 [off]
    ATTR_LIST = DateRangeType.startDate,startDate,,DateRangeType.endDate,endDate,,DateRangeType.startMonthDay,startMonthDay,,DateRangeType.endMonthDay,endMonthDay,
    -> DateFormatter_2 [off]
DateFormatter_2 [off]
    SRCFMT = Unknown - Automatic Detection
    FMT = FME Date (%Y%m%d)
    DATE_ATTR = endDate,startDate
    INVALID_DATE_VALUE = _FME_NO_OP_
    -> TQ_DateRange (writer GEOPACKAGE_2)
TQ_DateRange (writer GEOPACKAGE_2)
    attributes: parentFeature_ID text(50), timeInterval_ID mediumint, startDate datetime, endDate datetime, startMonthDay text(10), endMonthDay text(10)

Bookmark: NamedDate
ListExploder_3 [off]
    ATTR_CONFLICT_RES = Use Original
    ATTR_ACCUM_MODE = Merge Incoming List
    LIST_ATTR = TemporalPropertyType.namedDate{}
    INDEX_ATTR = _element_index
    LIST_FOUND -> AttributeRenamer_5 [off]
AttributeRenamer_5 [off]
    ATTR_LIST = TemporalPropertyType.namedDate,namedDate,
    -> TQ_NamedDate (writer GEOPACKAGE_2)
TQ_NamedDate (writer GEOPACKAGE_2)
    attributes: parentFeature_ID text(50), timeInterval_ID mediumint, namedDate text(20)

Bookmark: NamedDay
ListExploder_5 [off]
    ATTR_CONFLICT_RES = Use Original
    ATTR_ACCUM_MODE = Merge Incoming List
    LIST_ATTR = DayPropertyType.namedDay{}
    INDEX_ATTR = _element_index
    LIST_FOUND -> AttributeRenamer_6 [off]
AttributeRenamer_6 [off]
    ATTR_LIST = DayPropertyType.namedDay,namedDay,
    -> TQ_NamedDay (writer GEOPACKAGE_2)
TQ_NamedDay (writer GEOPACKAGE_2)
    attributes: parentFeature_ID text(50), timeInterval_ID mediumint, dayPeriod_ID mediumint, namedDay text(50)

Bookmark: NamedPeriod
ListExploder_6 [off]
    ATTR_CONFLICT_RES = Use Original
    ATTR_ACCUM_MODE = Merge Incoming List
    LIST_ATTR = DayPropertyType.namedPeriod{}
    INDEX_ATTR = _element_index
    LIST_FOUND -> AttributeRenamer_7 [off]
AttributeRenamer_7 [off]
    ATTR_LIST = DayPropertyType.namedPeriod,namedPeriod,
    -> TQ_NamedPeriod (writer GEOPACKAGE_2)
TQ_NamedPeriod (writer GEOPACKAGE_2)
    attributes: parentFeature_ID text(50), timeInterval_ID mediumint, dayPeriod_ID mediumint, namedPeriod text(50)

Bookmark: Time element
TQ_Day_Time_Join (writer GEOPACKAGE_2)
    attributes: parentFeature_ID text(50), timeInterval_ID mediumint, dayPeriod_ID mediumint, timePeriod_ID mediumint

Bookmark: TimeRange
ListExploder_8 [off]
    ATTR_CONFLICT_RES = Use Original
    ATTR_ACCUM_MODE = Merge Incoming List
    LIST_ATTR = TimePropertyType.timeRange{}
    INDEX_ATTR = _element_index
    LIST_FOUND -> AttributeRenamer_8 [off]
AttributeRenamer_8 [off]
    ATTR_LIST = TimeRangeType.startTime,startTime,,TimeRangeType.endTime,endTime,
    -> TQ_TimeRange (writer GEOPACKAGE_2)
TQ_TimeRange (writer GEOPACKAGE_2)
    attributes: parentFeature_ID text(50), timeInterval_ID mediumint, dayPeriod_ID mediumint, timePeriod_ID mediumint, startTime text(10), endTime text(10)

Bookmark: NamedTime
ListExploder_9 [off]
    ATTR_CONFLICT_RES = Use Original
    ATTR_ACCUM_MODE = Merge Incoming List
    LIST_ATTR = TimePropertyType.namedTime{}
    INDEX_ATTR = _element_index
    LIST_FOUND -> AttributeRenamer_9 [off]
AttributeRenamer_9 [off]
    ATTR_LIST = TimePropertyType.namedTime,namedTime,
    -> TQ_NamedTime (writer GEOPACKAGE_2)
TQ_NamedTime (writer GEOPACKAGE_2)
    attributes: parentFeature_ID text(50), timeInterval_ID mediumint, dayPeriod_ID mediumint, timePeriod_ID mediumint, namedTime text(50)
